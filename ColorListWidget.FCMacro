# FreeCAD Python Macro: Color List Widget
# This macro creates a dialog that allows users to manage colors
# and apply them to selected objects in FreeCAD

import FreeCAD as App
from PySide2 import QtWidgets, QtCore, QtGui


class ColorListWidget(QtWidgets.QDialog):
    def __init__(self):
        super().__init__()
        self.colors = []  # Store color names and RGB values
        self.init_ui()
        
    def init_ui(self):
        """Initialize the user interface."""
        self.setWindowTitle("FreeCAD Color Manager")
        self.setGeometry(100, 100, 400, 500)
        
        layout = QtWidgets.QVBoxLayout()
        
        # Label
        label = QtWidgets.QLabel("Colors:")
        layout.addWidget(label)
        
        # List widget to display colors
        self.color_list = QtWidgets.QListWidget()
        self.color_list.itemSelectionChanged.connect(self.on_selection_changed)
        layout.addWidget(self.color_list)
        
        # Buttons layout
        button_layout = QtWidgets.QHBoxLayout()
        
        # Add color button
        self.add_btn = QtWidgets.QPushButton("Add Color")
        self.add_btn.clicked.connect(self.add_color)
        button_layout.addWidget(self.add_btn)
        
        # Remove color button
        self.remove_btn = QtWidgets.QPushButton("Remove Color")
        self.remove_btn.clicked.connect(self.remove_color)
        self.remove_btn.setEnabled(False)
        button_layout.addWidget(self.remove_btn)
        
        layout.addLayout(button_layout)
        
        # Apply color button
        self.apply_btn = QtWidgets.QPushButton("Apply to Selected Object")
        self.apply_btn.clicked.connect(self.apply_color)
        self.apply_btn.setEnabled(False)
        self.apply_btn.setStyleSheet("font-weight: bold;")
        layout.addWidget(self.apply_btn)
        
        # Clear all button
        self.clear_btn = QtWidgets.QPushButton("Clear All")
        self.clear_btn.clicked.connect(self.clear_all)
        layout.addWidget(self.clear_btn)
        
        self.setLayout(layout)
        
    def add_color(self):
        """Open color dialog and add selected color to list."""
        color = QtWidgets.QColorDialog.getColor()
        if color.isValid():
            self.colors.append(color)
            item = QtWidgets.QListWidgetItem()
            item.setText(color.name())
            item.setBackground(color)
            # Set text color to white if background is dark
            if color.lightness() < 128:
                item.setForeground(QtGui.QColor(255, 255, 255))
            self.color_list.addItem(item)
            
    def remove_color(self):
        """Remove selected color from list."""
        current_row = self.color_list.currentRow()
        if current_row >= 0:
            self.color_list.takeItem(current_row)
            self.colors.pop(current_row)
            
    def clear_all(self):
        """Clear all colors from the list."""
        reply = QtWidgets.QMessageBox.question(
            self, 
            "Confirm", 
            "Clear all colors?",
            QtWidgets.QMessageBox.Yes | QtWidgets.QMessageBox.No
        )
        if reply == QtWidgets.QMessageBox.Yes:
            self.color_list.clear()
            self.colors.clear()
            
    def on_selection_changed(self):
        """Enable/disable buttons based on selection."""
        has_selection = self.color_list.currentRow() >= 0
        self.remove_btn.setEnabled(has_selection)
        self.apply_btn.setEnabled(has_selection)
        
    def apply_color(self):
        """Apply selected color to the currently selected FreeCAD object."""
        current_row = self.color_list.currentRow()
        if current_row < 0:
            QtWidgets.QMessageBox.warning(self, "Error", "No color selected.")
            return
            
        # Get selected color
        selected_color = self.colors[current_row]
        
        # Get selected objects in FreeCAD
        selected_objects = FreeCAD.Gui.Selection.getSelection()
        if not selected_objects:
            QtWidgets.QMessageBox.warning(
                self, 
                "Error", 
                "No object selected in FreeCAD.\nPlease select an object first."
            )
            return
        
        # Apply color to each selected object
        for obj in selected_objects:
            try:
                # Convert QColor to RGB tuple (normalized to 0-1)
                r = selected_color.red() / 255.0
                g = selected_color.green() / 255.0
                b = selected_color.blue() / 255.0
                
                # Set the color properties
                if hasattr(obj, "ViewObject"):
                    obj.ViewObject.ShapeColor = (r, g, b, 1.0)
                    
                color_name = selected_color.name()
                QtWidgets.QMessageBox.information(
                    self,
                    "Success",
                    f"Applied color {color_name} to {obj.Label}."
                )
            except Exception as e:
                QtWidgets.QMessageBox.critical(
                    self,
                    "Error",
                    f"Failed to apply color: {str(e)}"
                )


# Main execution
if __name__ == "__main__":
    dialog = ColorListWidget()
    dialog.exec_()
